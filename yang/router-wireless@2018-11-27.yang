module router-wireless {

    namespace "http://router.net/ns/yang/router-wireless";

    prefix "ro-ws";

    import ietf-yang-types {
      prefix yang;
    }

    description
        "This module defines wireless configuration used in OpenWrt routers.";

    revision "2018-11-27" {
        description
            "Version 0.1.0 -- Initial version.";
    }

    typedef channel-type {
        type enumeration {
            enum "auto";
            enum "1";
            enum "2";
            enum "3";
            enum "4";
            enum "5";
            enum "6";
            enum "7";
            enum "8";
            enum "9";
            enum "10";
            enum "11";
            enum "12";
            enum "13";
            enum "14";
            enum "15";
            enum "36";
            enum "40";
            enum "44";
            enum "48";
            enum "52";
            enum "56";
            enum "60";
            enum "64";
            enum "100";
            enum "104";
            enum "108";
            enum "112";
            enum "116";
            enum "132";
            enum "136";
            enum "140";
        }
    }

    container "devices" {
      description
        "Wireless devices.";

      list device {

        key "name";

        leaf name {
          type string;
        }

        leaf type {
           type string;
        }

        leaf country {
             type string;
             default "EU/13";
        }

        leaf channel {
             type channel-type;
             default "auto";
        }

        leaf wmm  {
             type boolean;
             default "true";
        }

        leaf txpower {
             type int32;
             default 100;
        }

        leaf dtim_period {
             type int32;
             default 1;
        }

        leaf beacon_int {
             type int32;
             default 100;
        }

        leaf maxassoc {
             type int32;
             default 32;
        }

        leaf hwmode {
             type string;
             default "auto";
        }

        leaf enabled {
             type boolean;
             description
              "enable/disable the interface";
             default true;
        }

        leaf frameburst {
             type boolean;
             default "false";
        }

        leaf doth {
             type int32;
        }

        list interface {
            key "name";

            description
              "List of configured interfaces on device";

            leaf name {
                type string;
                description
                 "Name of the uci config section. This is autogenerated by SWIG if it doesn't exist";
            }

            leaf device {
                 type string;
            }

            leaf ifname {
                 type string;
            }

            leaf network {
                 type string;
            }

            leaf mode {
                 type string;
                 default "ap";
            }

            leaf ssid {
                 type string;
            }

            leaf encryption {
                 description
                  "Wireless encryption method";
                 type string;
                 default "none";
            }

            leaf key {
                 type string;
            }

            leaf key1 {
                 type yang:hex-string {
                     length "10..26";
                 }
            }

            leaf key2 {
                 when "../encryption = 'wep-open'";
                 type yang:hex-string {
                     length "10..26";
                 }
            }

            leaf key3 {
                 when "../encryption = 'wep-open'";
                 type yang:hex-string {
                     length "10..26";
                 }
            }

            leaf key4 {
                 when "../encryption = 'wep-open'";
                 type yang:hex-string {
                     length "10..26";
                 }
            }

            leaf isolate {
                 type boolean;
                 default "false";
            }

            leaf enabled {
                type boolean;
                description
                 "enable/disable the interface";
                default true;
            }

            leaf macfilter {
                 type int32;
                 default 0;
            }

            leaf hidden {
                 type boolean;
                 description
                  "Turns off SSID broadcasting if set to true";
                 default false;
            }

          }
      }
    }
    container "devices-state" {

      config false;

      description
        "Wireless devices.";

      list device {

        key "name";

        leaf name {
          type string;
        }

        leaf channel {
          type channel-type;
        }

        leaf ssid {
          type string;
        }

        leaf encryption {
          type string;
        }

        leaf up {
          type boolean;
          description
            "Is the interface active or not.";
        }
      }
    }
}
